(defun c:EJ() (command"_insert""Q230023-20101_A_001 _ CarAtula_1.dwg""scale""1""rotate""0" "0,0" "1""1""1""0")(while (setq sset (ssget "X" '((0 . "INSERT")))) (sssetfirst nil sset) (C:Burst)) (princ) (command"_-purge""B""*""N")(command"_insert""Q230023-20101_A_002-004 _ Indice_2.dwg""scale""1""rotate""0" "500,0" "1""1""1""0")(while (setq sset (ssget "X" '((0 . "INSERT")))) (sssetfirst nil sset) (C:Burst)) (princ) (command"_-purge""B""*""N")(command"_insert""Q230023-20101_A_002-004 _ Indice_3.dwg""scale""1""rotate""0" "1000,0" "1""1""1""0")(while (setq sset (ssget "X" '((0 . "INSERT")))) (sssetfirst nil sset) (C:Burst)) (princ) (command"_-purge""B""*""N")(command"_insert""Q230023-20101_A_005-009 _ Esquemas_5.dwg""scale""1""rotate""0" "1500,0" "1""1""1""0")(while (setq sset (ssget "X" '((0 . "INSERT")))) (sssetfirst nil sset) (C:Burst)) (princ) (command"_-purge""B""*""N")(command"_insert""Q230023-20101_A_010-020 _ Constructivo_10.dwg""scale""1""rotate""0" "2000,0" "1""1""1""0")(while (setq sset (ssget "X" '((0 . "INSERT")))) (sssetfirst nil sset) (C:Burst)) (princ) (command"_-purge""B""*""N") )
